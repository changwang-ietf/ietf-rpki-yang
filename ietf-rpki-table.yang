module ietf-rpki-table {
  yang-version "1.1";
  namespace "urn:ietf:params:xml:ns:yang:ietf-rpki-table";
  prefix "rpki-table";
  import ietf-yang-types {
    prefix "yang";
    reference
      "RFC 6991: Common YANG Data Types.";
  }
  import ietf-inet-types {
    prefix "inet";
    reference
      "RFC 6991: Common YANG Data Types";
  }
  import ietf-routing {
    prefix rt;
    reference
      "RFC 8349: A YANG Data Model for Routing Management
       (NMDA Version).";
  }
  organization
    "IETF SIDROPS Working Group";
  contact
    "TBD";
  description
    "This module describes a YANG model for the Resource Public
     Key Infrastructure (RPKI) to Router Protocol configuration.
     This YANG model conforms to the Network Management
     Datastore Architecture (NMDA) as described in RFC 8342.
     Copyright (c) 2022 IETF Trust and the persons identified as
     authors of the code.  All rights reserved.
     Redistribution and use in source and binary forms, with or
     without modification, is permitted pursuant to, and subject to
     the license terms contained in, the Revised BSD License set
     forth in Section 4.c of the IETF Trust's Legal Provisions
     Relating to IETF Documents
     (https://trustee.ietf.org/license-info).
     This version of this YANG module is part of RFC XXXX;
     see the RFC itself for full legal notices.
     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference "RFC 8210";
  revision 2022-10-18 {
    description
      "Initial Version";
    reference
      "RFC 8210, YANG Data Model for RPKI to Router Protocol";
  }
  typedef ipv4-pfx-len {
    type uint8 {
      range "0 .. 32";
    }
    description
      "IPv4 Prefix Length.";
  }
  typedef ipv6-pfx-len {
    type uint8 {
      range "0 .. 128";
    }
    description
      "IPv6 Prefix Length.";
  }
  typedef subject-key-id {
    type binary {
      length 20;
    }
    description
      "Subject Key Identifier.";
  }
  grouping aspa-overall-records {
    description
      "ASPAs received from all RPKI cache servers.";
    list aspas {
      key "customer-asn";
      description
        "An entry of ASPA.";
      leaf customer-asn {
        type inet:as-number;
        description
          "The AS number of a customer.";
      }
      leaf server-address {
        type inet:ip-address;
        description
          "IP address of the RPKI cache server.";
      }
      list provider-asns {
        key "provider-asn";
        description
          "Providers of the customer.";
        leaf provider-asn {
          type inet:as-number;
          description
            "The AS number of a provider.";
        }
      }
    }
  }

  augment "/rt:routing" {
    description
      "RPKI tables augmentation of ietf-routing module.";
    container roa-tables {
      config false;
      description
        "List of tables containing ROAs received from all RPKI
         cache servers.";
      list roa-table {
        key "name";
        description
          "Table of ROAs received from all RPKI cache servers.";
        leaf name {
          type string;
          description
            "Name of the ROA table.";
        }
        container ipv4 {
          config false;
          description
            "Container for IPv4 ROAs table.";
          container roas {
            config false;
            description
              "ROAs received from the RPKI cache server.";
            list roa {
              key "prefix max-len asn source";
              description
                "An entry of ROA.";
              leaf prefix {
                type inet:ipv4-prefix;
                description
                  "The IPv4 prefix of the ROA.";
              }
              leaf max-len {
                type ipv4-pfx-len;
                description
                  "Denotes the longest prefix allowed. This
                   MUST NOT be less than the prefix length.";
              }
              leaf asn {
                type inet:as-number;
                description
                  "The origin AS number of the ROA.";
              }
              leaf source {
                type union {
                  type string;
                  type inet:ip-address;
                }
                description
                  "String representing the source of the records
                   in this record-set.";
              }
            }
          }
          leaf total-records {
            type yang:gauge32;
            description
              "Number of prefix policy records.";
          }
          leaf records-added {
            type yang:counter64;
            description
              "Number of prefix policy records cumulatively added.";
          }
          leaf records-deleted {
            type yang:counter64;
            description
              "Number of prefix policy records cumulatively
               deleted.";
          }
        }
        container ipv6 {
          config false;
          description
            "Container for IPv6 ROAs table.";
          container roas {
            config false;
            description
              "ROAs received from the RPKI cache server.";
            list roa {
              key "prefix max-len asn source";
              description
                "An entry of ROA.";
              leaf prefix {
                type inet:ipv6-prefix;
                description
                  "The IPv6 prefix of the ROA.";
              }
              leaf max-len {
                type ipv6-pfx-len;
                description
                  "Denotes the longest prefix allowed. This
                   MUST NOT be less than the prefix length.";
              }
              leaf asn {
                type inet:as-number;
                description
                  "The origin AS number of the ROA.";
              }
              leaf source {
                type union {
                  type string;
                  type inet:ip-address;
                }
                description
                  "Representing the source of the records in this
                   record-set. Either a server IP or a source file
                   of static records.";
              }
            }
          }
          leaf total-records {
            type yang:gauge32;
            description
              "Number of prefix policy records.";
          }
          leaf records-added {
            type yang:counter64;
            description
              "Number of prefix policy records cumulatively added.";
          }
          leaf records-deleted {
            type yang:counter64;
            description
              "Number of prefix policy records cumulatively
               deleted.";
          }
        }
      }
    }
    container router-key-tables {
      config false;
      description
        "List of router key table received from all RPKI cache
         servers.";
      list router-key-table {
        key "name";
        description
          "Table of router keys received from all RPKI cache
           servers.";
        leaf name {
          type string;
          description
            "Name of the router-key-table.";
        }
        container router-keys {
          config false;
          description
            "Router keys received from the RPKI cache server.";
          list router-key {
            key "ski asn key server-address";
            description
              "An entry of router key.";
            leaf ski {
              type subject-key-id;
              description
                "A router key's Subject Key Identifier (SKI).";
              reference
                "RFC 6487: A Profile for X.509 PKIX Resource
                 Certificates";
            }
            leaf asn {
              type inet:as-number;
              description
                "The AS number of the router which the key
                 belongs to.";
            }
            leaf key {
              type string;
              description
                "A router key's subjectPublicKeyInfo value.";
              reference
                "RFC 8608: BGPsec Algorithms, Key Formats, and
                 Signature Formats";
            }
            leaf server-address {
              type inet:ip-address;
              description
                "IP address of the RPKI cache server.";
            }
          }
        }
      }
    }
    container aspa-tables {
      config false;
      description
        "List of tables of ASPAs received from all RPKI cache
         servers.";
     list aspa-table {
        key "name";
        description
          "Table of ASPAs received from all RPKI cache servers.";
        leaf name {
          type string;
          description
            "Name of the ASPA-table.";
        }
        container ipv4 {
          config false;
          description
            "Container for IPv4 ASPAs table.";
          uses aspa-overall-records;
        }
        container ipv6 {
          config false;
          description
            "Container for IPv6 ASPAs table.";
          uses aspa-overall-records;
        }
      }
    }
  }
}
